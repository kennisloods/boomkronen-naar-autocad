FME workspace Boomkronen_naar_Autocad.fmw

Parameters:
- P_BRON_BOR_SHP = K:\GEODATA\Themadata\BOR\Data\SHP\Bomen_punten.shp   # Source Esri Shapefile(s)
- P_DOEL_ACAD = K:\SO\RW\Autocad\Projecten\Algemeen\Bomen_Boomkroongroottes_20181107.dwg   # Destination Autodesk AutoCAD DWG/DXF File
- P_TEMPLATE = $(FME_MF_DIR)Boom.dwg   # Template File
- P_LOG = K:\GEODATA\Kennisloods\Tools\VanLasnaarTekst\log\Boomkronen_naar_AutoCAD.log   # Log File

Readers:
- ESRISHAPE_1: ESRISHAPE from $(P_BRON_BOR_SHP)

Writers:
- ACAD_1: ACAD to $(P_DOEL_ACAD)

Bomen_punten (reader ESRISHAPE_1)
    attributes: ASSORTIM00 char(50), ASSORTIMEN long, BIJZONDE00 char(30), BIJZONDERE char(30), BUURT_NUMM short, BUURTNAAM char(30), DATUM_CREA date, DATUM_LAAT date, DIAMETER_K long, DIAMETER_S float, EIGENAAR char(50), EIGENAARS_ char(10), EIGENDOM char(50), EIGENDOMS_ char(10), GESLACHT char(50), ID long, INBOET char(2), JAAR_VAN_A long, NEDERLAN00 char(25), NEDERLANDS char(25), OBJ_ID long, ONDERHOUDS char(20), ONTWIKKE00 char(20), ONTWIKKELI char(20), RISICOGROE char(1), STANDPLA00 char(20), STANDPLAAT char(20), STRAAL_KRO float, STRAAT_NUM long, STRAATNAAM char(40),
      STRUCTUUR char(30), SUBBUURT_N short, THEMA char(40), VOLGNUMMER short, VORM char(40), WIJK_NUMME short, WIJKNAAM char(30), BEHEEROBJE char(30)
    -> DWGStyler
DWGStyler
    BLOCK_ROT = 0
    TEMPLATE_FILE = $(FME_MF_DIR)Boom.dwg
    BLOCK_SIZEY = @Value(DIAMETER_K)
    BLOCK_SIZEX = @Value(DIAMETER_K)
    BLOCK_SIZEZ = @Value(DIAMETER_K)
    BLOCK_NAME = boom
    BLOCK_SIZETYPE_DISPLAY = Scale Factor
    DWGStyled -> Bomen_punten (writer ACAD_1)
Bomen_punten (writer ACAD_1)
    attributes: ASSORTIM00 char(50), ASSORTIMEN number(11,0), BIJZONDE00 char(30), BIJZONDERE char(30), BUURT_NUMM number(6,0), BUURTNAAM char(30), DATUM_CREA char(8), DATUM_LAAT char(8), DIAMETER_K number(11,0), DIAMETER_S number(15,7), EIGENAAR char(50), EIGENAARS_ char(10), EIGENDOM char(50), EIGENDOMS_ char(10), GESLACHT char(50), ID number(11,0), INBOET char(2), JAAR_VAN_A number(11,0), NEDERLAN00 char(25), NEDERLANDS char(25), OBJ_ID number(11,0), ONDERHOUDS char(20), ONTWIKKE00 char(20), ONTWIKKELI char(20), RISICOGROE char(1), STANDPLA00 char(20), STANDPLAAT char(20), STRAAL_KRO number(15,7), STRAAT_NUM number(11,0), STRAATNAAM char(40),
      STRUCTUUR char(30), SUBBUURT_N number(6,0), THEMA char(40), VOLGNUMMER number(6,0), VORM char(40), WIJK_NUMME number(6,0), WIJKNAAM char(30), BEHEEROBJE char(30)
